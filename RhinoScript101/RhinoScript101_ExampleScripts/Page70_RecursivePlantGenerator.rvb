Option Explicit

'This script features an implementation of the recursive growth algorithm.
'A main subroutine was added (this one is missing from the primer, because
'it is very boring) to cater for the frontend.
'Comments have been added to this subroutine to explain the more exotic calls

'---------------------------------------------------------------------------------------
'-------------------------the code below does not appear in the primer------------------
'---------------------------------------------------------------------------------------

'We initialize a set of variables that hold 'sticky' growth properties
'Since we declare these variables OUTSIDE of any procedure block, they will
'remain active after the script completes. This means the settings are remembered
'between script runs but they will be erased whenever Rhino exits.
'They all start out being uninitialized (not assigned any value)

Dim prop_MinTwigCount
Dim prop_MaxTwigCount
Dim prop_MaxGenerations
Dim prop_MaxTwigLength
Dim prop_LengthMutation
Dim prop_MaxTwigAngle
Dim prop_AngleMutation

Call PlantGenerator()
Sub PlantGenerator()
    'Ask for a start point of the plant.
	Dim ptRoot : ptRoot = Rhino.GetPoint("Root point for plant")
	If IsNull(ptRoot) Then Exit Sub

    'Check all global variables for initialization and assign default
    'values if they have not yet been set. IsEmpty() can be used to
    'detect uninitialized variables (as opposed to IsNull() which is
    'used to detect faulty return values)
	If IsEmpty(prop_MinTwigCount)   Then prop_MinTwigCount = 0
	If IsEmpty(prop_MaxTwigCount)   Then prop_MaxTwigCount = 8
	If IsEmpty(prop_MaxGenerations) Then prop_MaxGenerations = 5
	If IsEmpty(prop_MaxTwigLength)  Then prop_MaxTwigLength = 10.0
	If IsEmpty(prop_LengthMutation) Then prop_LengthMutation = 0.75
	If IsEmpty(prop_MaxTwigAngle)   Then prop_MaxTwigAngle = 30.0
	If IsEmpty(prop_AngleMutation)  Then prop_AngleMutation = 0.85

    'We'll be using a temporary variable to collect data from the user.
    'We do this to prevent exposing the global variables to the frontend of Rhino
    Dim local_Value

    'Now collect all growth properties using a series of GetInteger and GetReal methods
    'This could be done a lot cleaner using an iterated Option getter, but that's a lot
    'more code. See chapter 8 on UI methods.
    
    'Some of these values have limits on their value. See the RhinoScript help
    'for information about the arguments.
	local_Value = Rhino.GetInteger("Minimum twig count", prop_MinTwigCount)
	If IsNull(local_Value) Then Exit Sub
	prop_MinTwigCount = local_Value
	
	local_Value = Rhino.GetInteger("Maximum twig count", prop_MaxTwigCount, 1)
	If IsNull(local_Value) Then Exit Sub
	prop_MaxTwigCount = local_Value

	local_Value = Rhino.GetInteger("Maximum branch generations", prop_MaxGenerations, 1, 1000)
	If IsNull(local_Value) Then Exit Sub
	prop_MaxGenerations = local_Value

	local_Value = Rhino.GetReal("Maximum twig length", prop_MaxTwigLength, 0.01)
	If IsNull(local_Value) Then Exit Sub
	prop_MaxTwigLength = local_Value

	local_Value = Rhino.GetReal("Twig length mutation", prop_LengthMutation, 0.01)
	If IsNull(local_Value) Then Exit Sub
	prop_LengthMutation = local_Value

	local_Value = Rhino.GetReal("Maximum twig angle", prop_MaxTwigAngle, 0.0, 90.0)
	If IsNull(local_Value) Then Exit Sub
	prop_MaxTwigAngle = local_Value

	local_Value = Rhino.GetReal("Twig angle mutation", prop_AngleMutation, 0.01)
	If IsNull(local_Value) Then Exit Sub
	prop_AngleMutation = local_Value

	'Assuming we made it this far (I.e. the user has not pressed Escape yet), randomize the
	'vbScript engine. It's a good idea to use the Randomize() function to make sure that random
	'sequences are not repeated.
	Call Randomize()

    'Turning of redraw will drastically speed up the tree generation. However, it's quite fun to watch
    'so you might consider switching it off.
	Call Rhino.EnableRedraw(False)

    'Collect all tree-growth variables into a single array.
    Dim GrowthProps
    GrowthProps = Array(prop_MinTwigCount, prop_MaxTwigCount, prop_MaxGenerations, _
                        prop_MaxTwigLength, prop_LengthMutation, prop_MaxTwigAngle, prop_AngleMutation)

    'Call the recursive function the first time. It will call itself from now on.
    'We also need to tell this first function that is has generation 1
    'We're assuming the growth direction at the root is vertical, 
    'so we have to supply a (0,0,1) direction vector.
	Call RecursiveGrowth(ptRoot, Array(0,0,1), GrowthProps, 1)

    'After all recursion has completed, be sure to enable the redraw again.
    Call Rhino.EnableRedraw(True)
End Sub

'---------------------------------------------------------------------------------------
'-------------------------the code below appears in the primer--------------------------
'---------------------------------------------------------------------------------------

Sub RecursiveGrowth(ByVal ptStart, ByVal vecDir, ByVal Props(), ByVal Generation)
    If Generation > Props(2) Then Exit Sub

    Dim ptGrow, vecGrow, newTwig
    
    'Copy and mutate the growth-properties
    Dim newProps : newProps = Props
    newProps(3) = Props(3) * Props(4)
    newProps(5) = Props(5) * Props(6)
    If newProps(5) > 90 Then newProps(5) = 90

    'Determine the number of twigs (could be less than zero)
    Dim N, maxN
    maxN = CInt(Props(0) + Rnd() * (Props(1) - Props(0)))

    For N = 1 To maxN
        ptGrow = RandomPointInCone(ptStart, vecDir, 0.25*Props(3), Props(3), Props(5))
        newTwig = AddArcDir(ptStart, ptGrow, vecDir)

        If Not IsNull(newTwig) Then
            vecGrow = Rhino.CurveTangent(newTwig, Rhino.CurveDomain(newTwig)(1))
            Call RecursiveGrowth(ptGrow, vecGrow, newProps, Generation+1)
        End If
    Next
End Sub

Function RandomPointInCone(ByVal Origin, ByVal Direction, ByVal MinDistance, ByVal MaxDistance, ByVal MaxAngle)
    Dim vecTwig
    vecTwig = Rhino.VectorUnitize(Direction)
    vecTwig = Rhino.VectorScale(vecTwig, MinDistance + Rnd() * (MaxDistance-MinDistance))

    Dim MutationPlane
    MutationPlane = Rhino.PlaneFromNormal(Array(0,0,0), vecTwig)

    vecTwig = Rhino.VectorRotate(vecTwig, Rnd() * maxAngle, MutationPlane(1))
    vecTwig = Rhino.VectorRotate(vecTwig, Rnd() * 360, Direction)

    RandomPointInCone = Rhino.PointAdd(Origin, vecTwig)
End Function

Function AddArcDir(ByVal ptStart, ByVal ptEnd, ByVal vecDir)
    AddArcDir = Null

    Dim vecBase : vecBase = Rhino.PointSubtract(ptEnd, ptStart)
    If Rhino.VectorLength(vecBase) = 0.0 Then Exit Function
    
    If Rhino.IsVectorParallelTo(vecBase, vecDir) Then
        AddArcDir = Rhino.AddLine(ptStart, ptEnd)
        Exit Function
    End If

    vecBase = Rhino.VectorUnitize(vecBase)
    vecDir = Rhino.VectorUnitize(vecDir)

    Dim vecBisector : vecBisector = Rhino.VectorAdd(vecDir, vecBase)
    vecBisector = Rhino.VectorUnitize(vecBisector)
    
    Dim dotProd : dotProd = Rhino.VectorDotProduct(vecBisector, vecDir)
    Dim midLength : midLength = (0.5 * Rhino.Distance(ptStart, ptEnd)) / dotProd
    
    vecBisector = Rhino.VectorScale(vecBisector, midLength)
    AddArcDir = Rhino.AddArc3Pt(ptStart, ptEnd, Rhino.PointAdd(ptStart, vecBisector))
End Function
