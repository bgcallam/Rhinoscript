Option Explicit

 Call ArrayObjectOnSurface()
 
  Sub ArrayObjectOnSurface()


    ' Get the surface object
    Dim srf : srf = Rhino.GetObject("Select surface", 8, vbTrue)
    If IsNull(srf) Then Exit Sub


    ' Get the number of rows
    Dim rows : rows = Rhino.GetInteger("Number of rows", 2, 2)
    If IsNull(rows) Then Exit Sub
    rows = rows - 1


    ' Get the number of columns
    Dim cols : cols = Rhino.GetInteger("Number of columns", 2, 2)
    If IsNull(cols) Then Exit Sub
    cols = cols - 1
    
    Rhino.UnselectAllObjects

    ' Select object to array
    Dim strObjID  
    strObjID = Rhino.GetObject("Select an Object", 4+8+16, True, True) 
    If IsNull(strObjID) Then Exit Sub

    ' Select Normal Base point
    Dim arrBasePt  
    arrBasePt = Rhino.GetPoint("Pick a base point for the Object") 
    If IsNull(arrBasePt) Then Exit Sub
    
    ' Select Normal End point
    Dim arrEndPt  
    arrEndPt = Rhino.GetPoint("Pick a point to define the object's orientation") 
    If IsNull(arrEndPt) Then Exit Sub
    
    'arrObjVector = Rhino.VectorUnitize(arrObjVector)  
    
    ' Get the domain of the surface
    Dim U : U = Rhino.SurfaceDomain(srf, 0)
    Dim V : V = Rhino.SurfaceDomain(srf, 1)
    If Not IsArray(U) Or Not IsArray(V) Then Exit Sub

    ' Turn off redrawing (faster)
    Rhino.EnableRedraw vbFalse

    ' Add the objects
    Dim i, j, t(1), pt, arrNormal, arrNormalEnd, obj
    For i = 0 To rows
      t(0) = U(0) + (((U(1) - U(0)) / rows) * i)
      For j = 0 To cols
        t(1) = V(0) + (((V(1) - V(0)) / cols) * j)
        pt = Rhino.EvaluateSurface(srf, t)
        If IsArray(pt) Then 
          Dim crossProduct, arrObjVector, strNewObject', arrAngle, objEnd
          
          ' Get the Normal Vector
          arrNormal = Rhino.SurfaceNormal(srf, t)
          
          ' Add our pt on the surface (t) to the Normal vector (move it)
          arrNormalEnd = Rhino.VectorAdd(arrNormal, pt)
          
          strNewObject = Rhino.OrientObject (strObjID, Array(arrBasePt, arrEndPt), Array(pt,arrNormalEnd), 1)
     
        End If
      Next
    Next


    ' Turn on redrawing
    Rhino.EnableRedraw vbTrue


  End Sub
